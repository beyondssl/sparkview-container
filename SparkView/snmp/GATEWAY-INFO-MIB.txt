--
-- This is RemoteSpark GATEWAY-INFO-MIB
--

GATEWAY-INFO-MIB DEFINITIONS ::= BEGIN

IMPORTS
    enterprises,
    MODULE-IDENTITY,
    OBJECT-TYPE,
    Integer32
        FROM SNMPv2-SMI
    DisplayString,
    TEXTUAL-CONVENTION
        FROM SNMPv2-TC
    MODULE-COMPLIANCE,
    OBJECT-GROUP
        FROM SNMPv2-CONF
    ;

-- Module Identity
------------------
gatewayMIB MODULE-IDENTITY
    -- Date Format is "YYYYMMDDhhmmZ"
    LAST-UPDATED "202112020000Z"
    ORGANIZATION "RemoteSpark"
    CONTACT-INFO "info@toremote.com"
    DESCRIPTION  "This is the MIB of RemoteSpark Gateway"
    -- Multiple pairs revision/description allowed
    REVISION     "202112020000Z"
    DESCRIPTION  "RemoteSpark Gateway MIB"
    -- 1.3.6.1.4.1.58667.10
    ::= { RemoteSpark 10 }

-- Enterprise OIDs
------------------
RemoteSpark OBJECT IDENTIFIER ::= { enterprises 58667 }

-- Textual Conventions
----------------------

-- Top-level tree (sections)
----------------------------
gatewayMIBObjects       OBJECT IDENTIFIER ::= { gatewayMIB 1 }
gatewayMIBConformance   OBJECT IDENTIFIER ::= { gatewayMIB 3 }

gatewayInfo				OBJECT IDENTIFIER ::= { gatewayMIBObjects 1 }

-- SECTION: Gateway Information (Scalar GET values)
--------------------
gatewayStaus OBJECT-TYPE
    SYNTAX      DisplayString
    MAX-ACCESS  read-only
    STATUS      current
    DESCRIPTION "Returns gateway current status"
    ::= { gatewayInfo 1 }

sessionCount OBJECT-TYPE
    SYNTAX      Integer32
    MAX-ACCESS  read-only
    STATUS      current
    DESCRIPTION "Session count (number of total connected sessions)."
    ::= { gatewayInfo 2 }

totalLicense OBJECT-TYPE
    SYNTAX      Integer32
    MAX-ACCESS  read-only
    STATUS      current
    DESCRIPTION "Total license granted to the gateway"
    ::= { gatewayInfo 3 }

licenseUsed OBJECT-TYPE
    SYNTAX      Integer32
    MAX-ACCESS  read-only
    STATUS      current
    DESCRIPTION "Returns used license number "
    ::= { gatewayInfo 4 }

--
-- SECTION: Conformance
--
compliance MODULE-COMPLIANCE
    STATUS  current
    DESCRIPTION
        "The compliance statement for SNMP entities which
        implement this MIB."
    MODULE  -- this module
    MANDATORY-GROUPS {
		objectGroup
    }
    ::= { gatewayMIBConformance 1 }

objectGroup OBJECT-GROUP
    OBJECTS {
        gatewayStaus,
        sessionCount,
        totalLicense,
        licenseUsed
    }
    STATUS current
    DESCRIPTION "A collection of object nodes in this MIB"
    ::= { gatewayMIBConformance 2 }

END
